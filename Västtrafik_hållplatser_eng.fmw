FME workspace Västtrafik_hållplatser_eng.fmw

Parameters:
- DestDataset_OGCGEOPACKAGE =
- DestDataset_OGCGEOPACKAGE_3 =

Writers:
- OGCGEOPACKAGE_1: OGCGEOPACKAGE to $(DestDataset_OGCGEOPACKAGE) in EPSG:3006
- OGCGEOPACKAGE_2: OGCGEOPACKAGE to $(DestDataset_OGCGEOPACKAGE_3) in EPSG:3006

Note: Authorisation is only valid for one hour at a time. You need to request a new one once it expires.
Note: Dont forget the parameters if you want to include optional data like coordinates
Note: How to request information about bus stops from an API comming from Swedish public transport company Västtrafik https://developer.vasttrafik.se/portal/#/
Creator
    GEOMTYPE = Geometry Object
    NUM = 1
    CREATED -> HTTPCaller

Bookmark: Gather data from API
HTTPCaller
    CONNECTION_TIMEOUT_LENGTH = 60
    CUSTOM_HEADERS = Accept;application/json Authorization;Bearer b4eef6d5-3ccd-3694-912a-24bf264c9b3c
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.vasttrafik.se/geo/v2/StopPoints?includeMunicipality=true&includeGeometry=true
    TRANSFER_TIMEOUT_LENGTH = 90
    USE_COOKIES = No
    VERIFY_SSL_CERTIFICATES = Yes
    -> JSONFragmenter

Bookmark: Extract bus stops
JSONFragmenter
    EXPLODE_FORMAT = JSON
    EXTRACT_ATTR = No
    JSON_ATTR = _response_body
    JSON_QUERY = json["stopPoints"][*]
    READ_FROM_FILE = NO
    REJECT_EMPTY_LISTS = YES
    FRAGMENTS -> JSONFormatter

Bookmark: To easily read the fragmented data
JSONFormatter
    ERROR_LIST_ATTR = _json_error
    FORMAT = Pretty Print
    INDENT_STYLE = 3 spaces
    JSON_DOCUMENT = @Value(_response_body)
    OUTPUT_ATTR = _formatted
    OUTPUT_ENCODING = UTF-8
    READ_FROM_FILE = NO
    REMOVE_EMPTY_OBJECTS_AND_ARRAYS = No
    REMOVE_EMPTY_STRINGS = No
    REMOVE_NULLS = No
    -> JSONFlattener

Bookmark: Attributes to expose
Note: Choose no in the option to recursively flatten to keep coordinate information etc
JSONFlattener
    ERROR_LIST_ATTR = _json_error
    JSON_DOCUMENT = @Value(_response_body)
    NEW_ATTRIBUTES = stopAreaGid stopAreaNumber number name shortName abbreviation designation localNumber municipality tariffZones transportAuthority isForBoardning isForAlighting isRegularTraffic isFlexibleBusService isFlexibleTaxiService isSpecialVehicleTransportConnectionPoint  geometry validFromDate validUpToDate
    READ_FROM_FILE = NO
    RECURSIVE = No
    -> JSONFlattener_2
Note: Request coordinates from geometry
JSONFlattener_2
    ERROR_LIST_ATTR = _json_error
    JSON_DOCUMENT = @Value(geometry)
    NEW_ATTRIBUTES = northingCoordinate eastingCoordinate
    READ_FROM_FILE = NO
    RECURSIVE = Yes
    -> JSONFlattener_3
Note: Additional optional parameters can be included
JSONFlattener_3
    ERROR_LIST_ATTR = _json_error
    JSON_DOCUMENT = @Value(municipality)
    NEW_ATTRIBUTES = code
    READ_FROM_FILE = NO
    RECURSIVE = Yes
    -> AttributeManager

Bookmark: Remove and sort for readability
AttributeManager
    ATTR_TABLE:
      REMOVE geometry
      REMOVE validUpToDate
      REMOVE validFromDate
      REMOVE _creation_instance
      REMOVE _response_body
      REMOVE _http_status_code
      REMOVE json_type
      REMOVE json_index
      REMOVE _formatted
      REMOVE municipality
      REMOVE tariffZones
      REMOVE transportAuthority
      REMOVE isSpecialVehicleTransportConnectionPoint
    -> Sorter
Sorter
    SORT_PARM = name ALPHA ASCENDING
    SORTED -> Table1 (writer OGCGEOPACKAGE_2)

Bookmark: Write to geopackage
Table1 (writer OGCGEOPACKAGE_2)
    attributes: stopAreaGid text, stopAreaNumber text, number text, name text, code text, shortName text, abbreviation text, designation text, localNumber text, isForBoardning text, isForAlighting text, isRegularTraffic text, isFlexibleBusService text, isFlexibleTaxiService text, eastingCoordinate text, northingCoordinate text
